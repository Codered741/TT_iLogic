'AUTHOR: Cody Redding 
'CONTACT: Codered741@gmail.com
'LAST MODIFIED: 20170721
'STATUS: In Progress
'LICENSE: Free to redistribute without authorization

'FUNCTION: Create a report of all "Make" parts that are missing drawings

Sub Main()

	SharedVariable("LogVar") = "Missing Drawings"
	iLogicVB.RunExternalRule("Write SV to Log.iLogicVB")
	
	MissingDrawings()
	
End Sub


Sub MissingDrawings()

	'check that the active document is an assembly file
	If ThisApplication.ActiveDocument.DocumentType <> kAssemblyDocumentObject Then
		MessageBox.Show("Please run this rule from the assembly file.", "iLogic")
		Exit Sub
	End If

	'declarations
	Dim oAsmDoc As AssemblyDocument 'define the active document as an assembly file
	oAsmDoc = ThisApplication.ActiveDocument
	
	Dim oRefDocs As New List(Of String)'DocumentsEnumerator = oAsmDoc.AllReferencedDocuments 'look at the files referenced by the assembly
	Dim oRefDocName As String
	Dim oRefDoc As Document
	
	'get list of part numbers from Structured BOM
	GetDocsFromBOM(oAsmDoc, oRefDocs)
	
	Dim oFile As String
	oFile = ThisDoc.PathAndFileName(False) & ".txt"
	Dim oAppend As System.IO.StreamWriter
	oAppend = IO.File.AppendText(oFile)
	
	Dim bFoundFile As Boolean
	bFoundFile = False

	
	Dim PrtsMissingDwgs As New List(Of String)
	Dim PrtsMissingMB As New List(Of String)
	
	
	'get user input
	RUsure = MessageBox.Show("This operation will search for drawing files that do NOT exist in your Vault workspace.  " _
		& vbLf & " Drawings may exist in the Vault, but will not be counted in this operation.  See a Vault Admin for assistance. " _
		& vbLf & " " _
		& vbLf & "Are you sure you want to create this report for all of the assembly components?" _
		& vbLf & "This operation could take some time.", "iLogic  - Batch Output TXT ", MessageBoxButtons.YesNo)
	
	' If RUsure = vbNo Then
		' Exit Sub
	' End If

	oAppend.WriteLine ("Report created - " & DateString & ":" & TimeString)  '& " by " & ThisApplication.UserName)
	'oAppend.Flush()
		
	'work the the drawing files for the referenced models
	'this expects that the model has a drawing of the same name
	For Each oRefDocName In oRefDocs
		oRefDoc = ThisApplication.Documents.ItemByName(oRefDocName)
		If oRefDoc.DocumentType = kPartDocumentObject OrElse oRefDoc.DocumentType = kAssemblyDocumentObject Then
			' Dim props as PropertySet
			props = oRefDoc.PropertySets.Item("Inventor User Defined Properties")
			
			Try 
				MBProp = props.Item("MakeBuy")
				
				If MBProp.Value = "Make" Then
				'check to see that the model has a drawing in the project workspace
				dwgPathName = FindDrawingFile(oRefDoc)
				
				If dwgPathName = "" Then 
					
					
					PrtsMissingDwgs.Add(oRefDoc.FullDocumentName)
					bFoundFile = True
					
				Else 
					
					'oAppend.WriteLine("FOUND : " & dwgPathName & " FOR : " & oRefDoc.FullDocumentName)
					
				End If
			End If
			Catch
			
				'oAppend.WriteLine("MAKE-BUY PROPERTY NOT FOUND : " & oRefDoc.FullDocumentName)
				PrtsMissingMB.Add(oRefDoc.FullDocumentName)
				bFoundFile = True
				
			End Try
			
			'MsgBox(MBProp.Value)
			
			
		End If
	Next
	
	'- - - - - - - - - - - - -
	If bFoundFile = True Then
		
		PrtsMissingDwgs.Sort()
		
		For Each doc In PrtsMissingDwgs
			oAppend.WriteLine("MISSING DRAWING FOR : " & doc)
		Next
		
		PrtsMissingMB.Sort()
		
		For Each doc In PrtsMissingMB
			oAppend.WriteLine("MAKE-BUY PROPERTY NOT FOUND : " & doc)
		Next
		
		oAppend.WriteLine("---End of Report---")
		oAppend.Flush()
		oAppend.Close()
		
		ThisDoc.Launch(oFile)
		
		If PrtsMissingDwgs.Count > 0 Then
			
			OpenSParts = MessageBox.Show("Would you like to open all the parts that are missing drawings?", "Open Parts?", MessageBoxButtons.YesNo, MessageBoxIcon.Question)
			If OpenSParts = vbYes Then
				For Each doc In PrtsMissingDwgs
					ThisApplication.Documents.Open(doc)
					ThisApplication.CommandManager.ControlDefinitions.Item("AppZoomAllCmd").Execute
				Next
			End If
		End If
		
		If PrtsMissingMB.Count > 0 Then

			
			OpenSParts = MessageBox.Show("Would you like to open all the parts that are missing Smart Part Properties?", "Open Parts?", MessageBoxButtons.YesNo, MessageBoxIcon.Question)
			If OpenSParts = vbYes Then
				For Each doc In PrtsMissingMB
					ThisApplication.Documents.Open(doc)
					ThisApplication.CommandManager.ControlDefinitions.Item("AppZoomAllCmd").Execute
				Next
			End If
		End If
		
	Else
	
		MessageBox.Show("No parts are missing drawings", "Good Job!")
		oAppend.WriteLine ("Nothing to Report")
		oAppend.WriteLine("---End of Report---")
		oAppend.Flush()
		oAppend.Close()
		
	End If
	
End Sub

Function FindDrawingFile(PartOrAssemblyDoc As Document)
    Dim fullFilename As String
    fullFilename = PartOrAssemblyDoc.fullFilename
   
    ' Extract the path from the full filename.
    Dim path As String
    path = Left$(fullFilename, InStrRev(fullFilename, "\"))
   
    ' Extract the filename from the full filename.
    Dim filename As String
    filename = Right$(fullFilename, Len(fullFilename) - InStrRev(fullFilename, "\"))
   
    ' Replace the extension with "dwg"
    filename = Left$(filename, InStrRev(filename, ".")) & "dwg"
   
    ' Find if the drawing exists.
    Dim drawingFilename As String
    drawingFilename = ThisApplication.DesignProjectManager.ResolveFile(path, filename)
   
    ' Check the result.
    If drawingFilename = "" Then
        ' Try again with idw extension.
        filename = Left$(filename, InStrRev(filename, ".")) & "idw"
       
        ' Find if the drawing exists.
        drawingFilename = ThisApplication.DesignProjectManager.ResolveFile(path, filename)
   
        ' Return the result.
        If drawingFilename <> "" Then
            FindDrawingFile = drawingFilename
        Else
            FindDrawingFile = ""
        End If
    Else
        ' Return the result.
        FindDrawingFile = drawingFilename
    End If
End Function


Sub GetDocsFromBOM(oDoc as Document, ByRef BOMDocs as List(of String))
	
	If oDoc.DocumentType <> kAssemblyDocumentObject Then
		MsgBox("This rule can only be run from an assembly")
		Exit Sub
	End If
	
	Dim oDocBOM As BOM = oDoc.ComponentDefinition.BOM

	oDocBOM.StructuredViewEnabled = True
	oDocBOM.StructuredViewFirstLevelOnly = False
	oDocBOM.PartsOnlyViewEnabled = False
	
	Dim oBOMView as BOMView = oDocBOM.BOMViews.Item("Structured")	
	Dim oBOMRows As BOMRowsEnumerator = oBOMView.BOMRows
	Dim oCompDef As ComponentDefinition
	Dim oPNProp as Inventor.Property
	
	For Each oRow as BOMRow in oBOMRows
		
			GetBOMRowDocFile(oRow, BOMDocs)
		
	Next 
	
	'BOMDocs.Sort()
	
End Sub
